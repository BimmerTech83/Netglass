--
-- Copyright (c) 2010 by Ruckus Wireless, Inc.
-- All Rights Reserved
--

RUCKUS-WLAN-MIB DEFINITIONS ::= BEGIN

IMPORTS
    ruckusCommonWLANModule
        FROM RUCKUS-ROOT-MIB
    RuckusAdminStatus,
    RuckusRadioMode,
    RuckusSSID,
    RuckusWEPKey,
    RuckusdB,
    RuckusWPAPassPhrase
        FROM RUCKUS-TC-MIB
    DisplayString,
    MacAddress,
    RowStatus,
    TruthValue
        FROM SNMPv2-TC
    OBJECT-GROUP
        FROM SNMPv2-CONF
    ifIndex,
    InterfaceIndex,
    IpAddress
        FROM IF-MIB
    MODULE-IDENTITY,
    OBJECT-TYPE,
    Counter32,
    Integer32,
    Unsigned32
        FROM SNMPv2-SMI;

ruckusWLANMIB MODULE-IDENTITY
    LAST-UPDATED "201010150800Z"
    ORGANIZATION "Ruckus Wireless, Inc."
    CONTACT-INFO
        "Ruckus Wireless, Inc.

        Postal:
        350 West Java Dr.
        Sunnyvale, CA 94089
        USA

        EMail: support@ruckuswireless.com

        Phone: +1-650-265-4200"
    DESCRIPTION
        "Ruckus WLAN mib"
    ::= { ruckusCommonWLANModule 1 }


-- Groups
--

ruckusWLANObjects OBJECT IDENTIFIER     ::= { ruckusWLANMIB 1 }

ruckusWLANInfo OBJECT IDENTIFIER    ::= { ruckusWLANObjects 1 }

ruckusWLANStaInfo OBJECT IDENTIFIER     ::= { ruckusWLANObjects 2 }

ruckusWLANSecurityInfo OBJECT IDENTIFIER    ::= { ruckusWLANObjects 3 }

-- ruckusWLANStatsInfo OBJECT IDENTIFIER    ::= { ruckusWLANObjects 4 }

ruckusWLANEvents OBJECT IDENTIFIER  ::= { ruckusWLANMIB 2 }

-- This is the WLAN table. Any WLAN updates and deletes should happen
-- through this table. But the WLAN creation is done using the
-- ruckusWLANRadioTable.
--

ruckusWLANTable OBJECT-TYPE
    SYNTAX  SEQUENCE OF RuckusWLANEntry
    MAX-ACCESS not-accessible
    STATUS current
    DESCRIPTION
        "WLAN table."
    ::= { ruckusWLANInfo 1 }


ruckusWLANEntry OBJECT-TYPE
    SYNTAX  RuckusWLANEntry
    MAX-ACCESS not-accessible
    STATUS current
    DESCRIPTION
        "Specifies each WLAN entry."
    INDEX {
        ruckusWLANIfIndex }
    ::= { ruckusWLANTable 1 }


RuckusWLANEntry ::= SEQUENCE {
	ruckusWLANIfIndex	   			 Unsigned32,
    ruckusWLANSSID                   RuckusSSID,
    ruckusWLANBSSID                  MacAddress,
    ruckusWLANBSSType                INTEGER,
    -- ruckusWLANOperationalRateSet     OCTET STRING(SIZE(1..255)),
    ruckusWLANOperationalRateSet     OCTET STRING,
    ruckusWLANBeaconPeriod           INTEGER,
    ruckusWLANDTIMPeriod             INTEGER,
    ruckusWLANRTSThreshold           INTEGER,
    ruckusWLANFragmentationThreshold INTEGER,
    ruckusWLANRadioMode              RuckusRadioMode,
    ruckusWLANChannel                INTEGER,
    ruckusWLANWDSEnable              TruthValue,
    ruckusWLANAdminStatus            INTEGER,
    ruckusWLANProtectionMode         INTEGER,
    ruckusWLANName                   DisplayString,
    ruckusWLANSSIDBcastDisable       TruthValue,
    ruckusWLANVlanID                 INTEGER,
    ruckusWLANRateShaper             DisplayString,
    ruckusWLANIGMPSnooping           INTEGER }

ruckusWLANIfIndex OBJECT-TYPE
    SYNTAX  Unsigned32 
    MAX-ACCESS read-only
    STATUS current
    DESCRIPTION
        "Interface index."
    ::= { ruckusWLANEntry 200 }

ruckusWLANSSID OBJECT-TYPE
    SYNTAX  RuckusSSID
    MAX-ACCESS read-write
    STATUS current
    DESCRIPTION
        "Specifies the name of the SSID."
    ::= { ruckusWLANEntry 1 }


ruckusWLANBSSID OBJECT-TYPE
    SYNTAX  MacAddress
    MAX-ACCESS read-only
    STATUS current
    DESCRIPTION
        "This attribute is the unique identifier in this BSS. 
        It is the 48-bit MAC address of the wireless interface."
    ::= { ruckusWLANEntry 2 }


ruckusWLANBSSType OBJECT-TYPE
    SYNTAX  INTEGER {
            station(1),
            master(2),
            independent(3) }
    MAX-ACCESS read-only
    STATUS current
    DESCRIPTION
        "Specifies the bss type."
    ::= { ruckusWLANEntry 3 }


ruckusWLANOperationalRateSet OBJECT-TYPE
    SYNTAX  OCTET STRING(SIZE(1..255))
    MAX-ACCESS read-only
    STATUS current
    DESCRIPTION
        "This attribute shall specify the set of data rates
        at which the station may transmit data.  Each octet
        contains a value representing a rate.  Each rate
        shall be within the range from 2 to 127,
        corresponding to data rates in increments of
        500 kb/s from 1 Mb/s to 63.5 Mb/s, and shall be
        supported (as indicated in the supported rates
        table) for receiving data. This value is reported in
        transmitted Beacon, Probe Request, Probe Response,
        Association Request, Association Response,
        Reassociation Request, and Reassociation Response
        frames, and is used to determine whether a BSS
        with which the station desires to synchronize is
        suitable. It is also used when starting a BSS,
        as specified in  10.3."
    ::= { ruckusWLANEntry 4 }


ruckusWLANBeaconPeriod OBJECT-TYPE
    SYNTAX  INTEGER (100..1000)
    UNITS
        "milli seconds"
    MAX-ACCESS read-only
    STATUS current
    DESCRIPTION
        "This attribute shall specify the number of milli seconds that a
        station shall use for scheduling Beacon transmissions.
        This value is transmitted in Beacon and Probe Response
        frames."
    ::= { ruckusWLANEntry 5 }


ruckusWLANDTIMPeriod OBJECT-TYPE
    SYNTAX  INTEGER (1..255)
    MAX-ACCESS read-only
    STATUS current
    DESCRIPTION
        "This attribute shall specify the number of TU that a
        station shall use for scheduling Beacon transmissions.
        This value is transmitted in Beacon and Probe Response
        frames."
    ::= { ruckusWLANEntry 6 }


ruckusWLANRTSThreshold OBJECT-TYPE
    SYNTAX  INTEGER (256..2346)
    MAX-ACCESS read-write
    STATUS current
    DESCRIPTION
        "This attribute shall indicate the number of octets in an
        MPDU, below which an RTS/CTS handshake shall not be
        performed, except as RTS/CTS is used as a cross modulation
        protection mechanism as defined in 9.10. An RTS/CTS
        handshake shall be performed at the beginning of any frame
        exchange sequence where the MPDU is of type Data or
        Management, the MPDU has an individual address in the
        Address1 field, and the length of the MPDU is greater than
        this threshold. (For additional details, refer to Table 21
        in 9.7.) Setting this attribute to be larger than the
        maximum MSDU size shall have the effect of turning off the
        RTS/CTS handshake for frames of Data or Management type
        transmitted by this STA. Setting this attribute to zero
        shall have the effect of turning on the RTS/CTS handshake
        for all frames of Data or Management type transmitted by
        this STA. The default value of this attribute shall be
        2347."
    ::= { ruckusWLANEntry 7 }


ruckusWLANFragmentationThreshold OBJECT-TYPE
    SYNTAX  INTEGER (256..2346)
    MAX-ACCESS read-write
    STATUS current
    DESCRIPTION
        "This attribute shall specify the current maximum size, in
        octets, of the MPDU that may be delivered to the PHY.
        An MSDU shall be broken into fragments if its size exceeds
        the value of this attribute after adding MAC headers and trailers.
        An MSDU or MMPDU shall be fragmented when the resulting
        frame has an individual address in the Address1 field,
        and the length of the frame is larger than this threshold.
        The default value for this attribute shall be the lesser of
        2346 or the aMPDUMaxLength of the attached PHY and
        shall never exceed the lesser of 2346 or the
        aMPDUMaxLength of the attached PHY. The value of this
        attribute shall never be less than 256."
    ::= { ruckusWLANEntry 8 }


ruckusWLANRadioMode OBJECT-TYPE
    SYNTAX  INTEGER{ ieee802dot11b(1), ieee802dot11g(2), auto(3), ieee802dot11a(4), ieee802dot11ng(5), ieee802dot11na(6), ieee802dot11ac(7), ieee802dot11ax(8), ieee802dot11be(9)}
    MAX-ACCESS read-only
    STATUS current
    DESCRIPTION
        "Specifies the radio mode. "
    ::= { ruckusWLANEntry 9 }


ruckusWLANChannel OBJECT-TYPE
    SYNTAX  INTEGER (1..14)
    MAX-ACCESS read-only
    STATUS current
    DESCRIPTION
        "Specifies the current operating channel."
    ::= { ruckusWLANEntry 10 }


ruckusWLANWDSEnable OBJECT-TYPE
    SYNTAX  TruthValue
    MAX-ACCESS read-write
    STATUS current
    DESCRIPTION
        "Specifies if the WDS is enabled or disabled on this interface.
        Allow 4 address mode of operation for an given WLAN interface."
    DEFVAL { false }
    ::= { ruckusWLANEntry 11 }


ruckusWLANAdminStatus OBJECT-TYPE
    SYNTAX  INTEGER {
            up(1),
            down(2) }
    MAX-ACCESS read-write
    STATUS current
    DESCRIPTION
        "Administrative status of the WLAN interface."
    ::= { ruckusWLANEntry 12 }


ruckusWLANProtectionMode OBJECT-TYPE
    SYNTAX  INTEGER {
            none(1),
            ctsOnly(2),
            ctsRts(3) }
    MAX-ACCESS read-only
    STATUS current
    DESCRIPTION
        "Enabled when 11g and 11b clients exist on the same network.
        none:
        Do not use any protection

        ctsOnly:
        AP will send a CTS frame prior to sending 11g frames.
        The CTS frame will silence 11b clients

        rtsCts:
        Require RTS to be sent by sender of 11g frame and responder
        to send CTS prior to any 11g frames being sent."
    ::= { ruckusWLANEntry 13 }


ruckusWLANName OBJECT-TYPE
    SYNTAX  OCTET STRING(SIZE(1..16))
    MAX-ACCESS read-write
    STATUS current
    DESCRIPTION
        "Specifies the name of the wlan."
    ::= { ruckusWLANEntry 14 }


ruckusWLANSSIDBcastDisable OBJECT-TYPE
    SYNTAX  TruthValue
    MAX-ACCESS read-write
    STATUS current
    DESCRIPTION
        "Setting to 1, cause  the ssid will not be broadcast in the beacons."
    DEFVAL { false }
    ::= { ruckusWLANEntry 15 }


ruckusWLANVlanID OBJECT-TYPE
    SYNTAX  INTEGER (1..4094)
    MAX-ACCESS read-write
    STATUS current
    DESCRIPTION
        "Specifies the VLAN ID of the WLAN.  If VLAN ID is 1, packets from this WLAN will be untagged."
    ::= { ruckusWLANEntry 16 }

ruckusWLANRateShaper OBJECT-TYPE
    SYNTAX  OCTET STRING(SIZE(1..31))
    MAX-ACCESS read-write
    STATUS current
    DESCRIPTION
        "This is controls fair access to the network. When enabled, the network traffic throughput 
        of each network device is limited to the rate specified in the traffic policy. Configuration format 
        (uplink/downlink)mbps or unlimited. Support values: 0.10mbps 0.25mbps 0.50mbps 0.75mbps 1.00mbps 1.25mbps 1.50mbps 1.75mbps 
        2.00mbps 2.25mbps 2.50mbps 2.75mbps 3.00mbps 3.25mbps 3.50mbps 3.75mbps 4.00mbps 4.25mbps 4.50mbps 4.75mbps 5.00mbps 5.25mbps 5.50mbps 
        5.75mbps 6.00mbps 6.25mbps 6.50mbps 6.75mbps 7.00mbps 7.25mbps 7.50mbps 7.75mbps 8.00mbps 8.25mbps 8.50mbps 8.75mbps 9.00mbps 9.25mbps 
        9.50mbps 9.75mbps 10.00mbps 10.25mbps 10.50mbps 10.75mbps 11.00mbps 11.25mbps 11.50mbps 11.75mbps 12.00mbps 12.25mbps 12.50mbps 
        12.75mbps 13.00mbps 13.25mbps 13.50mbps 13.75mbps 14.00mbps 14.25mbps 14.50mbps 14.75mbps 15.00mbps 15.25mbps 15.50mbps 15.75mbps 
        16.00mbps 16.25mbps 16.50mbps 16.75mbps 17.00mbps 17.25mbps 17.50mbps 17.75mbps 18.00mbps 18.25mbps 18.50mbps 18.75mbps 19.00mbps 
        19.25mbps 19.50mbps 19.75mbps 20.00mbps"
    ::= { ruckusWLANEntry 17 }

ruckusWLANIGMPSnooping OBJECT-TYPE
    SYNTAX  INTEGER {
            enable(1),
            disable(2)}
    MAX-ACCESS read-write
    STATUS current
    DESCRIPTION
        "Configure the IGMPSnooping for this WLAN. "
    ::= { ruckusWLANEntry 25 }

-- WLAN Suported Transmit Rates
--

ruckusWLANSuppDataRatesTxTable OBJECT-TYPE
    SYNTAX  SEQUENCE OF RuckusWLANSuppDataRatesTxEntry
    MAX-ACCESS not-accessible
    STATUS current
    DESCRIPTION
        "The Transmit bit rates supported by the PLCP and PMD,
        represented by a count from X'02-X'7f, corresponding to data
        rates in increments of 500Kb/s from 1 Mb/s to 63.5 Mb/s subject
        to limitations of each individual PHY."
    ::= { ruckusWLANInfo 2 }


ruckusWLANSuppDataRatesTxEntry OBJECT-TYPE
    SYNTAX  RuckusWLANSuppDataRatesTxEntry
    MAX-ACCESS not-accessible
    STATUS current
    DESCRIPTION
        "An Entry (conceptual row) in the dot11SupportedDataRatesTx
        Table."
    INDEX {
        ruckusWLANSuppDataRatesTxIndex }
    ::= { ruckusWLANSuppDataRatesTxTable 1 }


RuckusWLANSuppDataRatesTxEntry ::= SEQUENCE {

    ruckusWLANSuppDataRatesTxIndex Integer32,
    ruckusWLANSuppDataRatesTxValue DisplayString }


ruckusWLANSuppDataRatesTxIndex OBJECT-TYPE
    SYNTAX  Integer32
    MAX-ACCESS read-only
    STATUS current
    DESCRIPTION
        "Index object that identifies which data rate to access."
    ::= { ruckusWLANSuppDataRatesTxEntry 1 }


ruckusWLANSuppDataRatesTxValue OBJECT-TYPE
    SYNTAX  DisplayString
    MAX-ACCESS read-only
    STATUS current
    DESCRIPTION
        "The Transmit bit rates supported by the PLCP and PMD,
        represented by a count from X'02-X'7f, corresponding to data
        rates in increments of 500Kb/s from 1 Mb/s to 63.5 Mb/s subject
        to limitations of each individual PHY"
    ::= { ruckusWLANSuppDataRatesTxEntry 2 }


-- WLAN Suported Receive Rates
--

ruckusWLANSuppDataRatesRxTable OBJECT-TYPE
    SYNTAX  SEQUENCE OF RuckusWLANSuppDataRatesRxEntry
    MAX-ACCESS not-accessible
    STATUS current
    DESCRIPTION
        "The receive bit rates supported by the PLCP and PMD,
        represented by a count from X'02-X'7f, corresponding to data
        rates in increments of 500Kb/s from 1 Mb/s to 63.5 Mb/s.'"
    ::= { ruckusWLANInfo 3 }


ruckusWLANSuppDataRatesRxEntry OBJECT-TYPE
    SYNTAX  RuckusWLANSuppDataRatesRxEntry
    MAX-ACCESS not-accessible
    STATUS current
    DESCRIPTION
        "An Entry (conceptual row) in the
        dot11SupportedDataRatesRx Table."
    INDEX {
        ruckusWLANSuppDataRatesRxIndex }
    ::= { ruckusWLANSuppDataRatesRxTable 1 }


RuckusWLANSuppDataRatesRxEntry ::= SEQUENCE {

    ruckusWLANSuppDataRatesRxIndex Integer32,
    ruckusWLANSuppDataRatesRxValue DisplayString }


ruckusWLANSuppDataRatesRxIndex OBJECT-TYPE
    SYNTAX  Integer32
    MAX-ACCESS read-only
    STATUS current
    DESCRIPTION
        "Index object which identifies which data rate to access."
    ::= { ruckusWLANSuppDataRatesRxEntry 1 }


ruckusWLANSuppDataRatesRxValue OBJECT-TYPE
    SYNTAX  DisplayString
    MAX-ACCESS read-only
    STATUS current
    DESCRIPTION
        "The receive bit rates supported by the PLCP and PMD,
        represented by a count from X'02-X'7f, corresponding to data
        rates in increments of 500Kb/s from 1 Mb/s to 63.5 Mb/s."
    ::= { ruckusWLANSuppDataRatesRxEntry 2 }


-- WLAN Station Statistics-Hardware
--

ruckusWLANStaStatsTable OBJECT-TYPE
    SYNTAX  SEQUENCE OF RuckusWLANStaStatsEntry
    MAX-ACCESS not-accessible
    STATUS current
    DESCRIPTION
        "WLAN counter table."
    ::= { ruckusWLANStaInfo 1 }


ruckusWLANStaStatsEntry OBJECT-TYPE
    SYNTAX  RuckusWLANStaStatsEntry
    MAX-ACCESS not-accessible
    STATUS current
    DESCRIPTION
        "Specifies each wlan counter entry."
    INDEX {
        ruckusWLANStaStatsIndex,
        ruckusWLANStaStatsMacAddr }
    ::= { ruckusWLANStaStatsTable 1 }


RuckusWLANStaStatsEntry ::= SEQUENCE {

	ruckusWLANStaStatsIndex				InterfaceIndex,
    ruckusWLANStaStatsMacAddr           MacAddress,
    ruckusWLANStaStatsSSID              RuckusSSID,
    ruckusWLANStaStatsRxDataFrames      Counter32,
    ruckusWLANStaStatsRxMgmtFrames      Counter32,
    ruckusWLANStaStatsRxCtrlFrames      Counter32,
    ruckusWLANStaStatsRxUnicastFrames   Counter32,
    ruckusWLANStaStatsRxMulticastFrames Counter32,
    ruckusWLANStaStatsRxBytes           Counter32,
    ruckusWLANStaStatsRxDup             Counter32,
    ruckusWLANStaStatsRxNoPrivacy       Counter32,
    ruckusWLANStaStatsRxWEPFail         Counter32,
    ruckusWLANStaStatsRxDemicFail       Counter32,
    ruckusWLANStaStatsTxDecap           Counter32,
    ruckusWLANStaStatsRxDefrag          Counter32,
    ruckusWLANStaStatsTxDataFrames      Counter32,
    ruckusWLANStaStatsTxMgmtFrames      Counter32,
    ruckusWLANStaStatsTxUnicastFrames   Counter32,
    ruckusWLANStaStatsTxMulticastFrames Counter32,
    ruckusWLANStaStatsTxBytes           Counter32,
    ruckusWLANStaStatsTxAssoc           Counter32,
    ruckusWLANStaStatsTxAssocFail       Counter32,
    ruckusWLANStaStatsTxAuth            Counter32,
    ruckusWLANStaStatsTxAuthFail        Counter32,
    ruckusWLANStaStatsRSSI              Counter32,
    ruckusWLANStaStatsTxRxBytes         Counter32,
    ruckusWLANStaStatsTxRate            Unsigned32,
    ruckusWLANStaStatsRxRate            Unsigned32,
    ruckusWLANStaStatsTxDropRate        Unsigned32
         }

ruckusWLANStaStatsIndex OBJECT-TYPE
    SYNTAX  InterfaceIndex
    MAX-ACCESS read-only
    STATUS current
    DESCRIPTION
        "The index."
    ::= { ruckusWLANStaStatsEntry 200 }

ruckusWLANStaStatsMacAddr OBJECT-TYPE
    SYNTAX  MacAddress
    MAX-ACCESS read-only
    STATUS current
    DESCRIPTION
        "Specifies the station mac address."
    ::= { ruckusWLANStaStatsEntry 1 }


ruckusWLANStaStatsSSID OBJECT-TYPE
    SYNTAX  RuckusSSID
    MAX-ACCESS read-only
    STATUS current
    DESCRIPTION
        "station SSID."
    ::= { ruckusWLANStaStatsEntry 2 }


ruckusWLANStaStatsRxDataFrames OBJECT-TYPE
    SYNTAX  Counter32
    MAX-ACCESS read-only
    STATUS current
    DESCRIPTION
        "Rx data frames."
    ::= { ruckusWLANStaStatsEntry 3 }


ruckusWLANStaStatsRxMgmtFrames OBJECT-TYPE
    SYNTAX  Counter32
    MAX-ACCESS read-only
    STATUS current
    DESCRIPTION
        "Rx management frames."
    ::= { ruckusWLANStaStatsEntry 4 }


ruckusWLANStaStatsRxCtrlFrames OBJECT-TYPE
    SYNTAX  Counter32
    MAX-ACCESS read-only
    STATUS current
    DESCRIPTION
        "Rx control frames."
    ::= { ruckusWLANStaStatsEntry 5 }


ruckusWLANStaStatsRxUnicastFrames OBJECT-TYPE
    SYNTAX  Counter32
    MAX-ACCESS read-only
    STATUS current
    DESCRIPTION
        "Rx unicast frames."
    ::= { ruckusWLANStaStatsEntry 6 }


ruckusWLANStaStatsRxMulticastFrames OBJECT-TYPE
    SYNTAX  Counter32
    MAX-ACCESS read-only
    STATUS current
    DESCRIPTION
        "Rx multicast frames."
    ::= { ruckusWLANStaStatsEntry 7 }


ruckusWLANStaStatsRxBytes OBJECT-TYPE
    SYNTAX  Counter32
    MAX-ACCESS read-only
    STATUS current
    DESCRIPTION
        "Rx data count (bytes)."
    ::= { ruckusWLANStaStatsEntry 8 }


ruckusWLANStaStatsRxDup OBJECT-TYPE
    SYNTAX  Counter32
    MAX-ACCESS read-only
    STATUS current
    DESCRIPTION
        "Rx discarded because of duplicate."
    ::= { ruckusWLANStaStatsEntry 9 }


ruckusWLANStaStatsRxNoPrivacy OBJECT-TYPE
    SYNTAX  Counter32
    MAX-ACCESS read-only
    STATUS current
    DESCRIPTION
        "Rx with WEP but privacy off."
    ::= { ruckusWLANStaStatsEntry 10 }


ruckusWLANStaStatsRxWEPFail OBJECT-TYPE
    SYNTAX  Counter32
    MAX-ACCESS read-only
    STATUS current
    DESCRIPTION
        "Rx WEP processing failed."
    ::= { ruckusWLANStaStatsEntry 11 }


ruckusWLANStaStatsRxDemicFail OBJECT-TYPE
    SYNTAX  Counter32
    MAX-ACCESS read-only
    STATUS current
    DESCRIPTION
        "Rx demic failed."
    ::= { ruckusWLANStaStatsEntry 12 }


ruckusWLANStaStatsTxDecap OBJECT-TYPE
    SYNTAX  Counter32
    MAX-ACCESS read-only
    STATUS current
    DESCRIPTION
        "Rx decapsulation failed."
    ::= { ruckusWLANStaStatsEntry 13 }


ruckusWLANStaStatsRxDefrag OBJECT-TYPE
    SYNTAX  Counter32
    MAX-ACCESS read-only
    STATUS current
    DESCRIPTION
        "Rx defragmentation failed."
    ::= { ruckusWLANStaStatsEntry 14 }


ruckusWLANStaStatsTxDataFrames OBJECT-TYPE
    SYNTAX  Counter32
    MAX-ACCESS read-only
    STATUS current
    DESCRIPTION
        "Tx data frames."
    ::= { ruckusWLANStaStatsEntry 15 }


ruckusWLANStaStatsTxMgmtFrames OBJECT-TYPE
    SYNTAX  Counter32
    MAX-ACCESS read-only
    STATUS current
    DESCRIPTION
        "Tx management frames."
    ::= { ruckusWLANStaStatsEntry 16 }


ruckusWLANStaStatsTxUnicastFrames OBJECT-TYPE
    SYNTAX  Counter32
    MAX-ACCESS read-only
    STATUS current
    DESCRIPTION
        "Tx unicast frames."
    ::= { ruckusWLANStaStatsEntry 17 }


ruckusWLANStaStatsTxMulticastFrames OBJECT-TYPE
    SYNTAX  Counter32
    MAX-ACCESS read-only
    STATUS current
    DESCRIPTION
        "Tx multicast frames."
    ::= { ruckusWLANStaStatsEntry 18 }


ruckusWLANStaStatsTxBytes OBJECT-TYPE
    SYNTAX  Counter32
    MAX-ACCESS read-only
    STATUS current
    DESCRIPTION
        "Tx data count (bytes)."
    ::= { ruckusWLANStaStatsEntry 19 }


ruckusWLANStaStatsTxAssoc OBJECT-TYPE
    SYNTAX  Counter32
    MAX-ACCESS read-only
    STATUS current
    DESCRIPTION
        "Tx (re)associations."
    ::= { ruckusWLANStaStatsEntry 20 }


ruckusWLANStaStatsTxAssocFail OBJECT-TYPE
    SYNTAX  Counter32
    MAX-ACCESS read-only
    STATUS current
    DESCRIPTION
        "Tx (re)association failures"
    ::= { ruckusWLANStaStatsEntry 21 }


ruckusWLANStaStatsTxAuth OBJECT-TYPE
    SYNTAX  Counter32
    MAX-ACCESS read-only
    STATUS current
    DESCRIPTION
        "Tx (re)authentications."
    ::= { ruckusWLANStaStatsEntry 22 }


ruckusWLANStaStatsTxAuthFail OBJECT-TYPE
    SYNTAX  Counter32
    MAX-ACCESS read-only
    STATUS current
    DESCRIPTION
        "Tx (re)authentication failures."
    ::= { ruckusWLANStaStatsEntry 23 }


ruckusWLANStaStatsRSSI OBJECT-TYPE
    SYNTAX  Counter32
    MAX-ACCESS read-only
    STATUS current
    DESCRIPTION
        "Station RSSI."
    ::= { ruckusWLANStaStatsEntry 24 }


ruckusWLANStaStatsTxRxBytes OBJECT-TYPE
    SYNTAX  Counter32
    MAX-ACCESS read-only
    STATUS current
    DESCRIPTION
        "Total Tx and Rx data bytes  of last 5 min period."
    ::= { ruckusWLANStaStatsEntry 25 }


ruckusWLANStaStatsTxRate OBJECT-TYPE
    SYNTAX  Unsigned32
    UNITS
        "Bps"
    MAX-ACCESS read-only
    STATUS current
    DESCRIPTION
        "Tx data rate  of last 5 min period."
    ::= { ruckusWLANStaStatsEntry 26 }

ruckusWLANStaStatsRxRate OBJECT-TYPE
    SYNTAX  Unsigned32
    UNITS
        "Bps"
    MAX-ACCESS read-only
    STATUS current
    DESCRIPTION
        "Rx data rate  of last 5 min period."
    ::= { ruckusWLANStaStatsEntry 27 }


ruckusWLANStaStatsTxDropRate OBJECT-TYPE
    SYNTAX  Unsigned32
    MAX-ACCESS read-only
    STATUS current
    DESCRIPTION
        "Tx Packet drop rate."
    ::= { ruckusWLANStaStatsEntry 28 }



-- WLAN Station Information
--

ruckusWLANStaTable OBJECT-TYPE
    SYNTAX  SEQUENCE OF RuckusWLANStaEntry
    MAX-ACCESS not-accessible
    STATUS current
    DESCRIPTION
        "WLAN station table."
    ::= { ruckusWLANStaInfo 2 }


ruckusWLANStaEntry OBJECT-TYPE
    SYNTAX  RuckusWLANStaEntry
    MAX-ACCESS not-accessible
    STATUS current
    DESCRIPTION
        "Specifies each station entry."
    INDEX {
        ruckusWLANStaIndex,
        ruckusWLANStaAddr }
    ::= { ruckusWLANStaTable 1 }


RuckusWLANStaEntry ::= SEQUENCE {
	ruckusWLANStaIndex		InterfaceIndex,
    ruckusWLANStaAddr		MacAddress,
    ruckusWLANStaRssi    	Unsigned32,
    ruckusWLANStaErp     	Unsigned32,
    ruckusWLANState      	Unsigned32,
    ruckusWLANStaCapInfo 	Unsigned32,
    ruckusWLANStaAssocid 	Unsigned32,
    ruckusWLANStaOpMode  	Unsigned32,
    ruckusWLANStaIdle    	Unsigned32,
    ruckusWLANStaRates   	OCTET STRING,
    ruckusWLANStaIpaddr     OCTET STRING,
    ruckusWLANStaAuthMode   OCTET STRING
}

ruckusWLANStaIndex OBJECT-TYPE
    SYNTAX  InterfaceIndex
    MAX-ACCESS read-only
    STATUS current
    DESCRIPTION
        "The index."
    ::= { ruckusWLANStaEntry 200 }

ruckusWLANStaAddr OBJECT-TYPE
    SYNTAX  MacAddress
    MAX-ACCESS read-only
    STATUS current
    DESCRIPTION
        "An index into the table. Specifies each station address."
    ::= { ruckusWLANStaEntry 1 }

ruckusWLANStaRssi OBJECT-TYPE
    SYNTAX  Unsigned32
    MAX-ACCESS read-only
    STATUS current
    DESCRIPTION
        "Station RSSI."
    ::= { ruckusWLANStaEntry 2 }

ruckusWLANStaErp OBJECT-TYPE
    SYNTAX  Unsigned32
    MAX-ACCESS read-only
    STATUS current
    DESCRIPTION
        "Station ERP."
    ::= { ruckusWLANStaEntry 3 }

ruckusWLANState OBJECT-TYPE
    SYNTAX  Unsigned32
    MAX-ACCESS read-only
    STATUS current
    DESCRIPTION
        "Specifies station state."
    ::= { ruckusWLANStaEntry 4 }

ruckusWLANStaCapInfo OBJECT-TYPE
    SYNTAX  Unsigned32
    MAX-ACCESS read-only
    STATUS current
    DESCRIPTION
        "Specifies station capability information."
    ::= { ruckusWLANStaEntry 5 }

ruckusWLANStaAssocid OBJECT-TYPE
    SYNTAX  Unsigned32
    MAX-ACCESS read-only
    STATUS current
    DESCRIPTION
        "Specifies the station association id."
    ::= { ruckusWLANStaEntry 6 }

ruckusWLANStaOpMode OBJECT-TYPE
    SYNTAX  Unsigned32 {adhoc(0), station(1), wds(2),
    				 	oldadhoc(3), sap(6), monitor(8)}
    MAX-ACCESS read-only
    STATUS current
    DESCRIPTION
        "Specifies station operational mode:
         0, IBSS (adhoc) station;
         1, infrastructure station;
		 2, WDS link;
		 3, Old lucent compatible adhoc demo;
		 6, Software Access Point;
		 8, Monitor mode;"
    ::= { ruckusWLANStaEntry 7 }

ruckusWLANStaIdle OBJECT-TYPE
    SYNTAX  Unsigned32
    MAX-ACCESS read-only
    STATUS current
    DESCRIPTION
        "Specifies station idle time."
    ::= { ruckusWLANStaEntry 8 }

ruckusWLANStaRates OBJECT-TYPE
    SYNTAX  OCTET STRING (SIZE (1..127))
    MAX-ACCESS read-only
    STATUS current
    DESCRIPTION
        "Specifies station rates."
    ::= { ruckusWLANStaEntry 9 }

ruckusWLANStaIpaddr OBJECT-TYPE
    SYNTAX  OCTET STRING  (SIZE (2..40))
    MAX-ACCESS read-only
    STATUS current
    DESCRIPTION
        "Specifies Station IPv4 or IPv6 address."
    ::= { ruckusWLANStaEntry 16 }
    
ruckusWLANStaAuthMode OBJECT-TYPE
    SYNTAX   OCTET STRING
    MAX-ACCESS read-only
    STATUS current
    DESCRIPTION
        "Station Authentication Mode."
    ::= { ruckusWLANStaEntry 20 }

-- WLAN Station MQ Statistics
--

ruckusWLANStaMQTable OBJECT-TYPE
    SYNTAX  SEQUENCE OF RuckusWLANStaMQEntry
    MAX-ACCESS not-accessible
    STATUS current
    DESCRIPTION
        "Specifes ruckusWLANMQStatTable."
    ::= { ruckusWLANStaInfo 3 }


ruckusWLANStaMQEntry OBJECT-TYPE
    SYNTAX  RuckusWLANStaMQEntry
    MAX-ACCESS not-accessible
    STATUS current
    DESCRIPTION
        "Specifies each ruckusWLANMQStatEntry."
    INDEX {
        ruckusWLANStaMQIndex,
        ruckusWLANStaMQAddr,
        ruckusWLANStaMQQIndex }
    ::= { ruckusWLANStaMQTable 1 }


RuckusWLANStaMQEntry ::= SEQUENCE {

	ruckusWLANStaMQIndex			  InterfaceIndex,
    ruckusWLANStaMQAddr               MacAddress,
    ruckusWLANStaMQQIndex             Integer32,
    ruckusWLANStaMQPktsQueued         Unsigned32,
    ruckusWLANStaMQNumEnqueued        Unsigned32,
    ruckusWLANStaMQNumDequeued        Unsigned32,
    ruckusWLANStaMQNumRequeued        Unsigned32,
    ruckusWLANStaMQNumDropped         Unsigned32,
    ruckusWLANStaMQNumDeactivateQueue Unsigned32,
    ruckusWLANStaMQAveIpg             Unsigned32,
    ruckusWLANStaMQMinIpg             Unsigned32,
    ruckusWLANStaMQMaxIpg             Unsigned32,
    ruckusWLANStaMQAveTxLatency       Unsigned32,
    ruckusWLANStaMQMinTxLatency       Unsigned32,
    ruckusWLANStaMQMaxTxLatency       Unsigned32 }

ruckusWLANStaMQIndex OBJECT-TYPE
    SYNTAX  InterfaceIndex
    MAX-ACCESS read-only
    STATUS current
    DESCRIPTION
        "The index."
    ::= { ruckusWLANStaMQEntry 200 }

ruckusWLANStaMQAddr OBJECT-TYPE
    SYNTAX  MacAddress
    MAX-ACCESS read-only
    STATUS current
    DESCRIPTION
        "Station address."
    ::= { ruckusWLANStaMQEntry 1 }


ruckusWLANStaMQQIndex OBJECT-TYPE
    SYNTAX  Integer32 (1..4)
    MAX-ACCESS read-only
    STATUS current
    DESCRIPTION
        "Media queue index."
    ::= { ruckusWLANStaMQEntry 2 }


ruckusWLANStaMQPktsQueued OBJECT-TYPE
    SYNTAX  Unsigned32
    MAX-ACCESS read-only
    STATUS current
    DESCRIPTION
        "Frames currently queued."
    ::= { ruckusWLANStaMQEntry 3 }


ruckusWLANStaMQNumEnqueued OBJECT-TYPE
    SYNTAX  Unsigned32
    MAX-ACCESS read-only
    STATUS current
    DESCRIPTION
        "Total number of frames queued."
    ::= { ruckusWLANStaMQEntry 4 }


ruckusWLANStaMQNumDequeued OBJECT-TYPE
    SYNTAX  Unsigned32
    MAX-ACCESS read-only
    STATUS current
    DESCRIPTION
        "Total number of dequeued frames."
    ::= { ruckusWLANStaMQEntry 5 }


ruckusWLANStaMQNumRequeued OBJECT-TYPE
    SYNTAX  Unsigned32
    MAX-ACCESS read-only
    STATUS current
    DESCRIPTION
        "Total number of requeued frames."
    ::= { ruckusWLANStaMQEntry 6 }


ruckusWLANStaMQNumDropped OBJECT-TYPE
    SYNTAX  Unsigned32
    MAX-ACCESS read-only
    STATUS current
    DESCRIPTION
        "Drops due to queue overflow."
    ::= { ruckusWLANStaMQEntry 7 }


ruckusWLANStaMQNumDeactivateQueue OBJECT-TYPE
    SYNTAX  Unsigned32
    MAX-ACCESS read-only
    STATUS current
    DESCRIPTION
        "Total number of times queue deactivated."
    ::= { ruckusWLANStaMQEntry 8 }


ruckusWLANStaMQAveIpg OBJECT-TYPE
    SYNTAX  Unsigned32
    MAX-ACCESS read-only
    STATUS current
    DESCRIPTION
        "Average inter packet arrival time."
    ::= { ruckusWLANStaMQEntry 9 }


ruckusWLANStaMQMinIpg OBJECT-TYPE
    SYNTAX  Unsigned32
    MAX-ACCESS read-only
    STATUS current
    DESCRIPTION
        "Current max. inter packet arrival."
    ::= { ruckusWLANStaMQEntry 10 }


ruckusWLANStaMQMaxIpg OBJECT-TYPE
    SYNTAX  Unsigned32
    MAX-ACCESS read-only
    STATUS current
    DESCRIPTION
        "Current min. inter packet arrival."
    ::= { ruckusWLANStaMQEntry 11 }


ruckusWLANStaMQAveTxLatency OBJECT-TYPE
    SYNTAX  Unsigned32
    MAX-ACCESS read-only
    STATUS current
    DESCRIPTION
        "Average time to transmit frames from queue."
    ::= { ruckusWLANStaMQEntry 12 }


ruckusWLANStaMQMinTxLatency OBJECT-TYPE
    SYNTAX  Unsigned32
    MAX-ACCESS read-only
    STATUS current
    DESCRIPTION
        "Minimum time to transmit frames from queue."
    ::= { ruckusWLANStaMQEntry 13 }


ruckusWLANStaMQMaxTxLatency OBJECT-TYPE
    SYNTAX  Unsigned32
    MAX-ACCESS read-only
    STATUS current
    DESCRIPTION
        "Maximum time to transmit frames from queue."
    ::= { ruckusWLANStaMQEntry 14 }


-- WLAN Station Statistics-Ruckus
--

ruckusWLANStaRksTable OBJECT-TYPE
    SYNTAX  SEQUENCE OF RuckusWLANStaRksEntry
    MAX-ACCESS not-accessible
    STATUS current
    DESCRIPTION
        "Specifies ruckusWLANStaRksTable."
    ::= { ruckusWLANStaInfo 4 }


ruckusWLANStaRksEntry OBJECT-TYPE
    SYNTAX  RuckusWLANStaRksEntry
    MAX-ACCESS not-accessible
    STATUS current
    DESCRIPTION
        "Specifies each ruckusWLANStaRksEntry."
    INDEX {
        ruckusWLANStaRksIndex,
        ruckusWLANStaRksAddr }
    ::= { ruckusWLANStaRksTable 1 }


RuckusWLANStaRksEntry ::= SEQUENCE {

	ruckusWLANStaRksIndex			   InterfaceIndex,
    ruckusWLANStaRksAddr               MacAddress,
    ruckusWLANStaRksRxGoodFrames       Unsigned32,
    ruckusWLANStaRksRxCrcErrors        Unsigned32,
    ruckusWLANStaRksTxGoodFrames       Unsigned32,
    ruckusWLANStaRksTxRetries          Unsigned32,
    ruckusWLANStaRksTxDiscardExRetries Unsigned32,
    ruckusWLANStaRksTxRate             Unsigned32,
    ruckusWLANStaRksTxKbps             Unsigned32,
    ruckusWLANStaRksTxPer              Unsigned32,
    ruckusWLANStaRksTxRssi             RuckusdB     }

ruckusWLANStaRksIndex OBJECT-TYPE
    SYNTAX  InterfaceIndex
    MAX-ACCESS read-only
    STATUS current
    DESCRIPTION
        "The index."
    ::= { ruckusWLANStaRksEntry 200 }

ruckusWLANStaRksAddr OBJECT-TYPE
    SYNTAX  MacAddress
    MAX-ACCESS read-only
    STATUS current
    DESCRIPTION ""
    ::= { ruckusWLANStaRksEntry 1 }


ruckusWLANStaRksRxGoodFrames OBJECT-TYPE
    SYNTAX  Unsigned32
    MAX-ACCESS read-only
    STATUS current
    DESCRIPTION
        "number of rx frames without errors."
    ::= { ruckusWLANStaRksEntry 2 }


ruckusWLANStaRksRxCrcErrors OBJECT-TYPE
    SYNTAX  Unsigned32
    MAX-ACCESS read-only
    STATUS current
    DESCRIPTION
        "Number of rx frames with CRks errors."
    ::= { ruckusWLANStaRksEntry 3 }


ruckusWLANStaRksTxGoodFrames OBJECT-TYPE
    SYNTAX  Unsigned32
    MAX-ACCESS read-only
    STATUS current
    DESCRIPTION
        "Number of good tx frames acked."
    ::= { ruckusWLANStaRksEntry 4 }


ruckusWLANStaRksTxRetries OBJECT-TYPE
    SYNTAX  Unsigned32
    MAX-ACCESS read-only
    STATUS current
    DESCRIPTION
        "Number of retried frames."
    ::= { ruckusWLANStaRksEntry 5 }


ruckusWLANStaRksTxDiscardExRetries OBJECT-TYPE
    SYNTAX  Unsigned32
    MAX-ACCESS read-only
    STATUS current
    DESCRIPTION
        "Number of discarded frames due to excessive retries."
    ::= { ruckusWLANStaRksEntry 6 }


ruckusWLANStaRksTxRate OBJECT-TYPE
    SYNTAX  Unsigned32
    MAX-ACCESS read-only
    STATUS current
    DESCRIPTION
        "Current Phy Rate."
    ::= { ruckusWLANStaRksEntry 7 }


ruckusWLANStaRksTxKbps OBJECT-TYPE
    SYNTAX  Unsigned32
    MAX-ACCESS read-only
    STATUS current
    DESCRIPTION
        "Current transmit throughput."
    ::= { ruckusWLANStaRksEntry 8 }


ruckusWLANStaRksTxPer OBJECT-TYPE
    SYNTAX  Unsigned32
    MAX-ACCESS read-only
    STATUS current
    DESCRIPTION
        "Current Packet error rate."
    ::= { ruckusWLANStaRksEntry 9 }


ruckusWLANStaRksTxRssi OBJECT-TYPE
    SYNTAX  RuckusdB
    MAX-ACCESS read-only
    STATUS current
    DESCRIPTION
        "Rssi for ack'ed packets."
    ::= { ruckusWLANStaRksEntry 10 }


-- WLAN Security Information Group
-- WLAN Security Settings
-- This is a dependentruckusWLANSecurityTable expansion relationship table.
--

ruckusWLANSecurityTable OBJECT-TYPE
    SYNTAX  SEQUENCE OF RuckusWLANSecurityEntry
    MAX-ACCESS not-accessible
    STATUS current
    DESCRIPTION
        "Specifies WLAN security settings."
    ::= { ruckusWLANSecurityInfo 1 }


ruckusWLANSecurityEntry OBJECT-TYPE
    SYNTAX  RuckusWLANSecurityEntry
    MAX-ACCESS not-accessible
    STATUS current
    DESCRIPTION
        "Specifies each WLAN security entry."
    INDEX {
        ifIndex }
    ::= { ruckusWLANSecurityTable 1 }


RuckusWLANSecurityEntry ::= SEQUENCE {
    ruckusWLANSecurityMode                INTEGER,
    ruckusWLANSecurityAuthMode            INTEGER,
    ruckusWLANSecurityEncryMode           INTEGER
 }


ruckusWLANSecurityMode OBJECT-TYPE
    SYNTAX  INTEGER {
            none(1),
            wep(2),
            wpa(3) }
    MAX-ACCESS read-write
    STATUS current
    DESCRIPTION
        "Specifies the security mode.
         if wep, table ruckusWLANWEPTable should be configured firstly;
         if wpa + 'psk' auth,table ruckusWLANWPATable should be configured firstly;
         if wpa + 'eap-802-1x' or 'auto' auth,firstly configure ruckusWLANAAAServerTable,then configure ruckusWLANWPATable."
    DEFVAL { none }
    ::= { ruckusWLANSecurityEntry 5 }
    
ruckusWLANSecurityAuthMode OBJECT-TYPE
    SYNTAX  INTEGER {
            open(1),
            wep-shared(2),
            auto(3),
            wpa-eap-802-1x(4),
            sae(5),
            sae-psk(6),
            owe(7) }
    MAX-ACCESS read-write
    STATUS current
    DESCRIPTION
        "Specifies the security mode.
         if wep, only open;
         if wpa, open,wpa-eap-802-1x,auto ; for auto,is open,wpa-eap-802-1x; 
         if wpa2/wpa3-mixed, sae-psk, wpa-eap-802-1x;
         if wpa3, sae, wpa-eap-802-1x, owe;"
    DEFVAL { open }
    ::= { ruckusWLANSecurityEntry 8 }
    
ruckusWLANSecurityEncryMode OBJECT-TYPE
    SYNTAX  INTEGER {
            none(1),
            tkip(2),
            aes-ccmp(3),
            auto(4),
            aes-ccmp-256(5),
            aes-gcmp(6),
            aes-gcmp-256(7) }
    MAX-ACCESS read-write
    STATUS current
    DESCRIPTION
        "Specifies the security mode.
         if none, for wep/none;
         if tkip, for wpa ver1;
         if aes-ccmp, for wpa2, wpa3, and wpa2/wpa3-mixed;
         if auto, for wpa2, wpa auto[wpa+wpa2];
         if aes-ccmp-256, for wpa3, wpa2/wpa3-mixed;
         if aec-gcmp, for wpa3, wpa2/wpa3-mixed;
         if aes-gcmp-256, for wpa3, wpa2/wpa3-mixed;"
    DEFVAL { none }
    ::= { ruckusWLANSecurityEntry 10 }        


ruckusWLANWEPTable OBJECT-TYPE
    SYNTAX  SEQUENCE OF RuckusWLANWEPEntry
    MAX-ACCESS not-accessible
    STATUS current
    DESCRIPTION
        "Specifies WLAN WEP settings."
    ::= { ruckusWLANSecurityInfo 2 }


ruckusWLANWEPEntry OBJECT-TYPE
    SYNTAX  RuckusWLANWEPEntry
    MAX-ACCESS not-accessible
    STATUS current
    DESCRIPTION
        "Specifies each WLAN WEP entry."
    INDEX {
        ifIndex }
    ::= { ruckusWLANWEPTable 1 }


RuckusWLANWEPEntry ::= SEQUENCE {

    ruckusWLANWEPEncryLenType               INTEGER,
    ruckusWLANWEPKeyIndex               INTEGER,
    ruckusWLANWEPKey               DisplayString
 }


ruckusWLANWEPEncryLenType OBJECT-TYPE
    SYNTAX  INTEGER {
            bit-64(1),
            bit-128(2) }
    MAX-ACCESS read-write 
    STATUS current
    DESCRIPTION
        "Specifies the WEP encryption len type."
    DEFVAL { bit-128 }
    ::= { ruckusWLANWEPEntry 6 }

ruckusWLANWEPKeyIndex OBJECT-TYPE
    SYNTAX  INTEGER (1..4)
    MAX-ACCESS read-write 
    STATUS current
    DESCRIPTION
        "Specifies the WEP key index.
        For WEP,if one wlan has already used '1',
        so other wlans cannot use '1' again."
    ::= { ruckusWLANWEPEntry 8 }

ruckusWLANWEPKey OBJECT-TYPE
    SYNTAX  DisplayString (SIZE(3..32))
    MAX-ACCESS read-write 
    STATUS current
    DESCRIPTION
        "Specifies the WEP key.
        if ascII text,the length is 5 or 13,
        if Hexadecimal,the length is 10 or 26"
    ::= { ruckusWLANWEPEntry 9 }
   

ruckusWLANWPATable OBJECT-TYPE
    SYNTAX  SEQUENCE OF RuckusWLANWPAEntry
    MAX-ACCESS not-accessible
    STATUS current
    DESCRIPTION
        "Specifies WLAN WPA settings."
    ::= { ruckusWLANSecurityInfo 3 }


ruckusWLANWPAEntry OBJECT-TYPE
    SYNTAX  RuckusWLANWPAEntry
    MAX-ACCESS not-accessible
    STATUS current
    DESCRIPTION
        "Specifies each WLAN WPA entry."
    INDEX {
        ifIndex }
    ::= { ruckusWLANWPATable 1 }


RuckusWLANWPAEntry ::= SEQUENCE {

    ruckusWLANWPAVersion               INTEGER,
    ruckusWLANWPAKey               DisplayString,
    ruckusWLANWPASAEKey               DisplayString,
    ruckusWLANWPASAEH2EType               INTEGER,
    ruckusWLANWPARadiusNasId               DisplayString,
    ruckusWLANWPAReAuthenticationPeriod               INTEGER
 }


ruckusWLANWPAVersion OBJECT-TYPE
    SYNTAX  INTEGER {
            wpa(1),
            wpa2(2),
            auto(3),
            wpa3(4),
            wpa2-wpa3(5) }
    MAX-ACCESS read-write 
    STATUS current
    DESCRIPTION
        "Specifies the WPA version."
    DEFVAL { wpa }
    ::= { ruckusWLANWPAEntry 5 }
    
ruckusWLANWPAKey OBJECT-TYPE
    SYNTAX  DisplayString (SIZE(8..63))
    MAX-ACCESS read-write 
    STATUS current
    DESCRIPTION
        "Specifies the WPA key."
    ::= { ruckusWLANWPAEntry 12 }  
 
ruckusWLANWPASAEKey OBJECT-TYPE
    SYNTAX  DisplayString (SIZE(8..127))
    MAX-ACCESS read-write 
    STATUS current
    DESCRIPTION
        "Specifies the WPA SAE key for version 3."
    ::= { ruckusWLANWPAEntry 13 }
 
ruckusWLANWPASAEH2EType OBJECT-TYPE
    SYNTAX  INTEGER {
            disable(1),
            h2e-only(2),
            enable(3) }
    MAX-ACCESS read-write 
    STATUS current
    DESCRIPTION
        "Specifies the WPA SAE H2E Type for version3."
    DEFVAL { disable }
    ::= { ruckusWLANWPAEntry 14 }
         
ruckusWLANWPARadiusNasId OBJECT-TYPE
    SYNTAX  DisplayString (SIZE(1..64)) 
    MAX-ACCESS read-write 
    STATUS current
    DESCRIPTION
        "Specifies the WPA radius nas id(only for auth type is EAP_802.1x)."
    ::= { ruckusWLANWPAEntry 15 }  
    
ruckusWLANWPAReAuthenticationPeriod OBJECT-TYPE
    SYNTAX  INTEGER (30..3600)
    MAX-ACCESS read-write 
    STATUS current
    DESCRIPTION
        "Specifies the WPA radius reauthenticate period ,unit: second (only for auth type is EAP_802.1x)."
    DEFVAL { 600 }
    ::= { ruckusWLANWPAEntry 20 }    
          
    
ruckusWLANAAAServerTable OBJECT-TYPE
    SYNTAX  SEQUENCE OF RuckusWLANAAAServerEntry
    MAX-ACCESS not-accessible
    STATUS current
    DESCRIPTION
        "Specifies WLAN AAA server settings."
    ::= { ruckusWLANSecurityInfo 4 }


ruckusWLANAAAServerEntry OBJECT-TYPE
    SYNTAX  RuckusWLANAAAServerEntry
    MAX-ACCESS not-accessible
    STATUS current
    DESCRIPTION
        "Specifies each WLAN AAA server entry."
    INDEX {
        ifIndex,
        ruckusWLANSeverMode
         }
    ::= { ruckusWLANAAAServerTable 1 }


RuckusWLANAAAServerEntry ::= SEQUENCE {
    ruckusWLANSeverMode                    INTEGER,
    ruckusWLANServerIpAddress              OCTET STRING,
    ruckusWLANServerPort                   INTEGER,
    ruckusWLANServerSecret                 OCTET STRING
 }

ruckusWLANSeverMode OBJECT-TYPE
    SYNTAX  INTEGER {
            auth(1),
            account(2) }
    MAX-ACCESS not-accessible
    STATUS current
    DESCRIPTION
        "Specifies the AAA server mode:1,authenticate server;2,account server."
    ::= { ruckusWLANAAAServerEntry 2 }
  

ruckusWLANServerIpAddress OBJECT-TYPE
    SYNTAX  OCTET STRING  (SIZE (2..40))    
    MAX-ACCESS read-write 
    STATUS current
    DESCRIPTION
        "Specifies the AAA server ip(v4 and v6) address."
    DEFVAL {0}
    ::= { ruckusWLANAAAServerEntry 10 }

ruckusWLANServerPort OBJECT-TYPE
    SYNTAX  INTEGER 
    MAX-ACCESS read-write 
    STATUS current
    DESCRIPTION
        "Specifies the AAA server port."
    DEFVAL {1812}
    ::= { ruckusWLANAAAServerEntry 12 }
    
ruckusWLANServerSecret OBJECT-TYPE
    SYNTAX  OCTET STRING(SIZE(1..255)) 
    MAX-ACCESS read-write 
    STATUS current
    DESCRIPTION
        "Specifies the AAA server access secret."
    ::= { ruckusWLANAAAServerEntry 15 }    

    

-- Conformance & Compliance
--
 
--
--                  
-- new added MIBs for China Telecom
ruckusWLANStatsTable OBJECT-TYPE
    SYNTAX  SEQUENCE OF RuckusWLANStatsEntry
    MAX-ACCESS not-accessible
    STATUS current
    DESCRIPTION
        "WLAN statistics table"
    ::= { ruckusWLANInfo 4 }


ruckusWLANStatsEntry OBJECT-TYPE
    SYNTAX  RuckusWLANStatsEntry
    MAX-ACCESS not-accessible
    STATUS current
    DESCRIPTION
        "Specifies each WLAN statictics entry."
    INDEX {
        ruckusWLANStatsIndex }
    ::= { ruckusWLANStatsTable 1 }


RuckusWLANStatsEntry ::= SEQUENCE {
	ruckusWLANStatsIndex				InterfaceIndex,
    ruckusWLANStatsSSID                 RuckusSSID,
    ruckusWLANStatsBSSID                MacAddress,
    ruckusWLANStatsNumSta               Counter32,
    ruckusWLANStatsNumAuthSta           Counter32,
    ruckusWLANStatsNumAuthReq           Counter32,
    ruckusWLANStatsNumAuthResp          Counter32,
    ruckusWLANStatsNumAuthSuccess       Counter32,
    ruckusWLANStatsNumAuthFail          Counter32,
    ruckusWLANStatsNumAssocReq          Counter32,
    ruckusWLANStatsNumAssocResp         Counter32,
    ruckusWLANStatsNumReAssocReq        Counter32,
    ruckusWLANStatsNumReAssocResp       Counter32,
    ruckusWLANStatsNumAssocSuccess      Counter32,
    ruckusWLANStatsNumAssocFail         Counter32,
    ruckusWLANStatsAssocFailRate        Unsigned32,
    ruckusWLANStatsAuthFailRate         Unsigned32,
    ruckusWLANStatsAssocSuccessRate     Unsigned32,
    ruckusWLANStatsRxDataFrames         Counter32,
    ruckusWLANStatsRxMgmtFrames         Counter32,
    ruckusWLANStatsRxCtrlFrames         Counter32,
    ruckusWLANStatsRxUnicastFrames      Counter32,
    ruckusWLANStatsRxMulticastFrames    Counter32,
    ruckusWLANStatsRxBroadcastFrames    Counter32,
    ruckusWLANStatsRxBytes              Counter32,
    ruckusWLANStatsRxDup                Counter32,
    ruckusWLANStatsRxNoPrivacy          Counter32,
    ruckusWLANStatsRxWEPFail            Counter32,
--    ruckusWLANStatsRxDemicFail        Counter32,
--    ruckusWLANStatsRxDecap            Counter32,
--    ruckusWLANStatsRxDefrag           Counter32,
--    ruckusWLANStatsRxCRCError         Counter32,
    ruckusWLANStatsRxDecryptCRCError    Counter32,
    ruckusWLANStatsRxMICError           Counter32,
    ruckusWLANStatsRxDrops              Counter32,
    ruckusWLANStatsRxErrors             Counter32,
    ruckusWLANStatsRxFrames             Counter32,
    ruckusWLANStatsRxDropRate           Unsigned32,
    ruckusWLANStatsTxDataFrames         Counter32,
    ruckusWLANStatsTxMgmtFrames         Counter32,
    ruckusWLANStatsTxUnicastFrames      Counter32,
    ruckusWLANStatsTxMulticastFrames    Counter32,
    ruckusWLANStatsTxBroadcastFrames    Counter32,
    ruckusWLANStatsTxBytes              Counter32,
    ruckusWLANStatsTxDrops              Counter32,
    ruckusWLANStatsTxErrors             Counter32,
    ruckusWLANStatsTxFrames             Counter32,
    ruckusWLANStatsPeriodRxErrorRate    Unsigned32,
    ruckusWLANStatsPeriodTxErrorRate    Unsigned32,
    ruckusWLANStatsPeriodAssocReq       Counter32,
    ruckusWLANStatsPeriodAssocResp      Counter32,
    ruckusWLANStatsPeriodAssocSuccess   Counter32,
    ruckusWLANStatsTotalAssocTime       TimeTicks
}

ruckusWLANStatsIndex OBJECT-TYPE
    SYNTAX  InterfaceIndex
    MAX-ACCESS read-only
    STATUS current
    DESCRIPTION
        "The index."
    ::= { ruckusWLANStatsEntry 200 }

ruckusWLANStatsSSID OBJECT-TYPE
    SYNTAX  RuckusSSID
    MAX-ACCESS read-only
    STATUS current
    DESCRIPTION
        "station SSID."
    ::= { ruckusWLANStatsEntry 1 }


ruckusWLANStatsBSSID OBJECT-TYPE
    SYNTAX  MacAddress
    MAX-ACCESS read-only
    STATUS current
    DESCRIPTION
        "Wlan BSSID."
    ::= { ruckusWLANStatsEntry 2 }


ruckusWLANStatsNumSta OBJECT-TYPE
    SYNTAX  Counter32
    MAX-ACCESS read-only
    STATUS current
    DESCRIPTION
        "Number of associated stations."
    ::= { ruckusWLANStatsEntry 3 }


ruckusWLANStatsNumAuthSta OBJECT-TYPE
    SYNTAX  Counter32
    MAX-ACCESS read-only
    STATUS current
    DESCRIPTION
        "Number of authenticated stations."
    ::= { ruckusWLANStatsEntry 4 }
    
                    
ruckusWLANStatsNumAuthReq OBJECT-TYPE
    SYNTAX  Counter32
    MAX-ACCESS read-only
    STATUS current
    DESCRIPTION
        "Number of authentication requests."
    ::= { ruckusWLANStatsEntry 5 }
                    
 
ruckusWLANStatsNumAuthResp OBJECT-TYPE
    SYNTAX  Counter32
    MAX-ACCESS read-only
    STATUS current
    DESCRIPTION
        "Number of authentication responses."
    ::= { ruckusWLANStatsEntry 6 }
                    

ruckusWLANStatsNumAuthSuccess OBJECT-TYPE
    SYNTAX  Counter32
    MAX-ACCESS read-only
    STATUS current
    DESCRIPTION
        "Number of successful authentications."
    ::= { ruckusWLANStatsEntry 7 }
                    

ruckusWLANStatsNumAuthFail OBJECT-TYPE
    SYNTAX  Counter32
    MAX-ACCESS read-only
    STATUS current
    DESCRIPTION
        "Number of authentication failures."
    ::= { ruckusWLANStatsEntry 8 }
                    

ruckusWLANStatsNumAssocReq OBJECT-TYPE
    SYNTAX  Counter32
    MAX-ACCESS read-only
    STATUS current
    DESCRIPTION
        "Number of association requests."
    ::= { ruckusWLANStatsEntry 9 }
                    

ruckusWLANStatsNumAssocResp OBJECT-TYPE
    SYNTAX  Counter32
    MAX-ACCESS read-only
    STATUS current
    DESCRIPTION
        "Number of association responses."
    ::= { ruckusWLANStatsEntry 10 }
                    

ruckusWLANStatsNumReAssocReq OBJECT-TYPE
    SYNTAX  Counter32
    MAX-ACCESS read-only
    STATUS current
    DESCRIPTION
        "Number of reassociation requests."
    ::= { ruckusWLANStatsEntry 11 }
                    

ruckusWLANStatsNumReAssocResp OBJECT-TYPE
    SYNTAX  Counter32
    MAX-ACCESS read-only
    STATUS current
    DESCRIPTION
        "Number of reassociation responses."
    ::= { ruckusWLANStatsEntry 12 }
                    

ruckusWLANStatsNumAssocSuccess OBJECT-TYPE
    SYNTAX  Counter32
    MAX-ACCESS read-only
    STATUS current
    DESCRIPTION
        "Number of successful associations."
    ::= { ruckusWLANStatsEntry 13 }
                    

ruckusWLANStatsNumAssocFail OBJECT-TYPE
    SYNTAX  Counter32
    MAX-ACCESS read-only
    STATUS current
    DESCRIPTION
        "Number of association failures."
    ::= { ruckusWLANStatsEntry 14 }
                    

ruckusWLANStatsAssocFailRate OBJECT-TYPE
    SYNTAX  Unsigned32
    UNITS
        "percentage"
    MAX-ACCESS read-only
    STATUS current
    DESCRIPTION
        "Station association fail rate. ruckusWLANStatsNumAssocFail/ruckusWLANStatsNumAssocReq"
    ::= { ruckusWLANStatsEntry 15 }


ruckusWLANStatsAuthFailRate  OBJECT-TYPE
    SYNTAX  Unsigned32
    UNITS
        "percentage"
    MAX-ACCESS read-only
    STATUS current
    DESCRIPTION
        "Station authentication fail rate. ruckusWLANStatsNumAuthFail/ruckusWLANStatsNumAuthReq"
    ::= { ruckusWLANStatsEntry 16 }


ruckusWLANStatsAssocSuccessRate OBJECT-TYPE
    SYNTAX  Unsigned32
    UNITS
        "percentage"
    MAX-ACCESS read-only
    STATUS current
    DESCRIPTION
        "Station association success rate. ruckusWLANStatsNumAssocSuccess/ruckusWLANStatsNumAssocReq"
    ::= { ruckusWLANStatsEntry 17 }


ruckusWLANStatsRxDataFrames OBJECT-TYPE
    SYNTAX  Counter32
    MAX-ACCESS read-only
    STATUS current
    DESCRIPTION
        "Count of received data frames."
    ::= { ruckusWLANStatsEntry 18 }
                    

ruckusWLANStatsRxMgmtFrames OBJECT-TYPE
    SYNTAX  Counter32
    MAX-ACCESS read-only
    STATUS current
    DESCRIPTION
        "Count of received management frames."
    ::= { ruckusWLANStatsEntry 19 }
                    

ruckusWLANStatsRxCtrlFrames OBJECT-TYPE
    SYNTAX  Counter32
    MAX-ACCESS read-only
    STATUS current
    DESCRIPTION
        "Count of received contrl frames."
    ::= { ruckusWLANStatsEntry 20 }
                    

ruckusWLANStatsRxUnicastFrames OBJECT-TYPE
    SYNTAX  Counter32
    MAX-ACCESS read-only
    STATUS current
    DESCRIPTION
        "Count of received unicast frames."
    ::= { ruckusWLANStatsEntry 21 }
                    

ruckusWLANStatsRxMulticastFrames  OBJECT-TYPE
    SYNTAX  Counter32
    MAX-ACCESS read-only
    STATUS current
    DESCRIPTION
        "Count of received multicast frames."
    ::= { ruckusWLANStatsEntry 22 }
                    
ruckusWLANStatsRxBroadcastFrames  OBJECT-TYPE
    SYNTAX  Counter32
    MAX-ACCESS read-only
    STATUS current
    DESCRIPTION
        "Count of received broadcast frames."
    ::= { ruckusWLANStatsEntry 23 }
                    
ruckusWLANStatsRxBytes OBJECT-TYPE
    SYNTAX  Counter32
    MAX-ACCESS read-only
    STATUS current
    DESCRIPTION
        "Count of received bytes."
    ::= { ruckusWLANStatsEntry 24 }
                    
ruckusWLANStatsRxDup OBJECT-TYPE
    SYNTAX  Counter32
    MAX-ACCESS read-only
    STATUS current
    DESCRIPTION
        "Count of received duplicated frames."
    ::= { ruckusWLANStatsEntry 25 }
                    
ruckusWLANStatsRxNoPrivacy OBJECT-TYPE
    SYNTAX  Counter32
    MAX-ACCESS read-only
    STATUS current
    DESCRIPTION
        "Count of received frames without privacy bit enabled."
    ::= { ruckusWLANStatsEntry 26 }
                    
ruckusWLANStatsRxWEPFail OBJECT-TYPE
    SYNTAX  Counter32
    MAX-ACCESS read-only
    STATUS current
    DESCRIPTION
        "Count of received failured WEP frames."
    ::= { ruckusWLANStatsEntry 27 }
                    
ruckusWLANStatsRxDecryptCRCError OBJECT-TYPE
    SYNTAX  Counter32
    MAX-ACCESS read-only
    STATUS current
    DESCRIPTION
        "Count of received frames with decrypted CRC error."
    ::= { ruckusWLANStatsEntry 28 }
                    
ruckusWLANStatsRxMICError OBJECT-TYPE
    SYNTAX  Counter32
    MAX-ACCESS read-only
    STATUS current
    DESCRIPTION
        "Count of received frames with MIC error."
    ::= { ruckusWLANStatsEntry 29 }

ruckusWLANStatsRxDrops OBJECT-TYPE
    SYNTAX  Counter32
    MAX-ACCESS read-only
    STATUS current
    DESCRIPTION
        "Count of received frame drops."
    ::= { ruckusWLANStatsEntry 30 }


ruckusWLANStatsRxErrors OBJECT-TYPE
    SYNTAX  Counter32
    MAX-ACCESS read-only
    STATUS current
    DESCRIPTION
        "Count of received error frames."
    ::= { ruckusWLANStatsEntry 31 }


ruckusWLANStatsRxFrames OBJECT-TYPE
    SYNTAX  Counter32
    MAX-ACCESS read-only
    STATUS current
    DESCRIPTION
        "Count of received frames."
    ::= { ruckusWLANStatsEntry 32 }


ruckusWLANStatsRxDropRate OBJECT-TYPE
    SYNTAX  Unsigned32
    UNITS
        "percentage"
    MAX-ACCESS read-only
    STATUS current
    DESCRIPTION
        "Received frame drop rate. ruckusWLANStatsRxDrops/ruckusWLANStatsRxFrames"
    ::= { ruckusWLANStatsEntry 33 }


                   
ruckusWLANStatsTxDataFrames OBJECT-TYPE
    SYNTAX  Counter32
    MAX-ACCESS read-only
    STATUS current
    DESCRIPTION
        "Count of transmitted data frames."
    ::= { ruckusWLANStatsEntry 34 }
                    
ruckusWLANStatsTxMgmtFrames OBJECT-TYPE
    SYNTAX  Counter32
    MAX-ACCESS read-only
    STATUS current
    DESCRIPTION
        "Count of transmitted management frames."
    ::= { ruckusWLANStatsEntry 35 }
                    
ruckusWLANStatsTxUnicastFrames OBJECT-TYPE
    SYNTAX  Counter32
    MAX-ACCESS read-only
    STATUS current
    DESCRIPTION
        "Count of transmitted unicast frames."
    ::= { ruckusWLANStatsEntry 36 }
                    
ruckusWLANStatsTxMulticastFrames OBJECT-TYPE
    SYNTAX  Counter32
    MAX-ACCESS read-only
    STATUS current
    DESCRIPTION
        "Count of transmitted multicast frames."
    ::= { ruckusWLANStatsEntry 37 }
                    
ruckusWLANStatsTxBroadcastFrames OBJECT-TYPE
    SYNTAX  Counter32
    MAX-ACCESS read-only
    STATUS current
    DESCRIPTION
        "Count of transmitted broadcast frames."
    ::= { ruckusWLANStatsEntry 38 }
                    
ruckusWLANStatsTxBytes OBJECT-TYPE
    SYNTAX  Counter32
    MAX-ACCESS read-only
    STATUS current
    DESCRIPTION
        "Count of transmitted bytes."
    ::= { ruckusWLANStatsEntry 39 }
                    
ruckusWLANStatsTxDrops OBJECT-TYPE
    SYNTAX  Counter32
    MAX-ACCESS read-only
    STATUS current
    DESCRIPTION
        "Count of transmitted frame drops."
    ::= { ruckusWLANStatsEntry 40 }


ruckusWLANStatsTxErrors OBJECT-TYPE
    SYNTAX  Counter32
    MAX-ACCESS read-only
    STATUS current
    DESCRIPTION
        "Count of transmitted error frames."
    ::= { ruckusWLANStatsEntry 41 }


ruckusWLANStatsTxFrames OBJECT-TYPE
    SYNTAX  Counter32
    MAX-ACCESS read-only
    STATUS current
    DESCRIPTION
        "Count of total transmitted frames."
    ::= { ruckusWLANStatsEntry 42 }

ruckusWLANStatsPeriodRxErrorRate OBJECT-TYPE
    SYNTAX  Unsigned32
    UNITS
        "percentage"
    MAX-ACCESS read-only
    STATUS current
    DESCRIPTION
        "RX packet error rate. 
        ruckusWLANStatsRxErrors/ruckusWLANStatsRxFrames of last 5 min period
        "
    ::= { ruckusWLANStatsEntry 43 }

ruckusWLANStatsPeriodTxErrorRate OBJECT-TYPE
    SYNTAX  Unsigned32
    UNITS
        "percentage"
    MAX-ACCESS read-only
    STATUS current
    DESCRIPTION
        "TX packet error rate. 
        ruckusWLANStatsTxErrors/ruckusWLANStatsTxFrames of last 5 min period"
    ::= { ruckusWLANStatsEntry 44 }

ruckusWLANStatsPeriodAssocReq OBJECT-TYPE
    SYNTAX  Counter32
    MAX-ACCESS read-only
    STATUS current
    DESCRIPTION
        "Number of association requests of last 5 min period."
    ::= { ruckusWLANStatsEntry 45 }
                    

ruckusWLANStatsPeriodAssocResp OBJECT-TYPE
    SYNTAX  Counter32
    MAX-ACCESS read-only
    STATUS current
    DESCRIPTION
        "Number of association responses of last 5 min period."
    ::= { ruckusWLANStatsEntry 46 }
                    

ruckusWLANStatsPeriodAssocSuccess OBJECT-TYPE
    SYNTAX  Counter32
    MAX-ACCESS read-only
    STATUS current
    DESCRIPTION
        "Number of successful associations of last 5 min period."
    ::= { ruckusWLANStatsEntry 47 }


ruckusWLANStatsTotalAssocTime OBJECT-TYPE
    SYNTAX  TimeTicks
    MAX-ACCESS read-only
    STATUS current
    DESCRIPTION
        "WLAN Stats client total association time"
    ::= { ruckusWLANStatsEntry 49 }
END
